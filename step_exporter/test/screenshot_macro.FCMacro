# FreeCAD截图宏
import FreeCAD
import FreeCADGui
import Import
import os

# 从环境变量读取参数
step_file = os.environ.get('STEP_FILE', '')
output_image = os.environ.get('OUTPUT_IMAGE', '')
width = int(os.environ.get('IMAGE_WIDTH', '1920'))
height = int(os.environ.get('IMAGE_HEIGHT', '1080'))

print(f"STEP_FILE: {step_file}")
print(f"OUTPUT_IMAGE: {output_image}")

if step_file and output_image:
    try:
        doc = FreeCAD.newDocument("Screenshot")
        Import.insert(step_file, doc.Name)
        doc.recompute()
        
        objects = doc.Objects
        print(f"Found {len(objects)} objects")
        
        # 确保输出目录存在
        output_dir = os.path.dirname(output_image)
        if output_dir and not os.path.exists(output_dir):
            os.makedirs(output_dir, exist_ok=True)
        
        # 截图
        view = FreeCADGui.ActiveDocument.ActiveView
        view.viewAxonometric()
        view.fitAll()
        
        import time
        time.sleep(2)
        
        view.saveImage(output_image, width, height, "White")
        print(f"SUCCESS: Screenshot saved to {output_image}")
        
        FreeCAD.closeDocument(doc.Name)
    except Exception as e:
        print(f"ERROR: {e}")
        import traceback
        traceback.print_exc()
    
    # 退出FreeCAD
    FreeCADGui.getMainWindow().close()
else:
    print("ERROR: STEP_FILE or OUTPUT_IMAGE not set")
